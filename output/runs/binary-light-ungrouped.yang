module binary-light {
  yang-version 1.1;
  namespace "http://example.com/upnp-yang-schema/binary-light";
  prefix "binary-light";
  organization "upnp-yang-test";
  contact "upnp-yang-test";
  description
  "binary-light";
  revision 2024-06-27 {
    reference "RFC 8407";
  }
  container binary-light {
    description "binary-light";
    container device {
      config false;
      description "Device description";
      leaf device-type {
        type string;
        description "Device type";
      }
      leaf friendly-name {
        type string;
        description "Name";
      }
      leaf manufacturer {
        type string;
        description "Manufacturer";
      }
      leaf manufacturer-URL {
        type string;
        description "Manufacturer URL";
      }
      leaf model-description {
        type string;
        description "Model description";
      }
      leaf model-name {
        type string;
        description "Model name";
      }
      leaf model-number {
        type string;
        description "Model number";
      }
      leaf model-URL {
        type string;
        description "Model URL";
      }
      leaf serial-number {
        type string;
        description "Serial number";
      }
      leaf UDN {
        type string;
        description "UUID";
      }
      leaf UPC {
        type string;
        description "UPC";
      }
      list icon-list {
        key "url";
        description  "Icons";
        leaf mimetype {
          type string;
          description "MIME type";
        }
        leaf width {
          type uint32;
          description "Width";
        }
        leaf height {
          type uint32;
          description "Height";
        }
        leaf depth {
          type uint32;
          description "Color depth";
        }
        leaf url {
          type string;
          description "URL";
        }
      }
      leaf presentation-url {
        type string;
        description "Presentation URL";
      }
    }
    container services {
      description "Services";
      container switch-power {
        description "Service";
        container state {
          description "State table";
          leaf target {
            type boolean;
            default false;
            description "Target";
          }
          leaf status {
            type boolean;
            default false;
            config false;
            description "Status";
          }
        }
        container state-attributes {
          config false;
          description "Read-only attributes";
          container target {
            description "Variable attributes";
            uses send-events-grouping;
          }
          container status {
            description "Variable attributes";
            uses send-events-grouping;
          }
        }
        action set-target {
          description "Action SetTarget";
          input {
            leaf new-target-value {
              type boolean;
              description "Related to Target";
            }
          }
        }
        action get-target {
          description "Action GetTarget";
          output {
            leaf ret-target-value {
              type leafref {
                path "../../state/target";
              }
              description "Related to Target";
            }
          }
        }
        action get-status {
          description "Action GetStatus";
          output {
            leaf result-status {
              type leafref {
                path "../../state/status";
              }
              description "Related to Status";
            }
          }
        }
      }
    }
    container devices {
      description "Embedded devices";
    }
  }
  grouping send-events-grouping {
    description "Send event attribute";
    leaf send-events {
      type boolean;
      description "Send event attribute";
    }
  }
}
