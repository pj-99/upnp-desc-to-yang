module embed-device-example {
  yang-version 1.1;
  namespace "http://example.com/upnp-yang-schema/embed-device-example";
  prefix "embed-device-example";
  organization "upnp-yang-test";
  contact "upnp-yang-test";
  description
  "embed-device-example";
  revision 2024-06-27 {
    reference "RFC 8407";
  }

  grouping embed-device-example-top {
    description "embed-device-example";
    container embed-device-example {
      description "embed-device-example";
      uses embed-device-example-desc-top;
      uses embed-device-example-services-top;
      uses embed-device-example-devices-top;
    }

  }

  grouping embed-device-example-desc-top {
    description "Device description";
    container device {
      config false;
      description "Device description";
      leaf device-type {
        type string;
        description "Device type";
      }

      leaf friendly-name {
        type string;
        description "Name";
      }

      leaf manufacturer {
        type string;
        description "Manufacturer";
      }

      leaf manufacturer-URL {
        type string;
        description "Manufacturer URL";
      }

      leaf model-description {
        type string;
        description "Model description";
      }

      leaf model-name {
        type string;
        description "Model name";
      }

      leaf model-number {
        type string;
        description "Model number";
      }

      leaf model-URL {
        type string;
        description "Model URL";
      }

      leaf serial-number {
        type string;
        description "Serial number";
      }

      leaf UDN {
        type string;
        description "UUID";
      }

      leaf UPC {
        type string;
        description "UPC";
      }

      list icon-list {
        key "url";
        description  "Icons";
        leaf mimetype {
          type string;
          description "MIME type";
        }

        leaf width {
          type uint32;
          description "Width";
        }

        leaf height {
          type uint32;
          description "Height";
        }

        leaf depth {
          type uint32;
          description "Color depth";
        }

        leaf url {
          type string;
          description "URL";
        }

      }

      leaf presentation-url {
        type string;
        description "Presentation URL";
      }

    }

  }

  grouping embed-device-example-services-top {
    description "Services";
    container services {
      description "Services";
      uses switch-power-top;
    }

  }

  grouping switch-power-state-top {
    description "State table";
    container state {
      description "State table";
      leaf target {
        type boolean;
        default false;
        description "Target";
      }

      leaf status {
        type boolean;
        default false;
        config false;
        description "Status";
      }

    }

  }

  grouping switch-power-state-attributes-top {
    description "Table attributes";
    container state-attributes {
      config false;
      description "Read-only attributes";
      container target {
        description "Variable attributes";
        uses state-variable-attributes;
      }

      container status {
        description "Variable attributes";
        uses state-variable-attributes;
      }

    }

  }

  grouping switch-power-action {
    description "Service actions";
    action set-target {
      description "Action SetTarget";
      input {
        leaf new-target-value {
          type boolean;
          description "Related to Target";
        }

      }

    }

    action get-target {
      description "Action GetTarget";
      output {
        leaf ret-target-value {
          type leafref {
            path "../../state/target";
          }

          description "Related to Target";
        }

      }

    }

    action get-status {
      description "Action GetStatus";
      output {
        leaf result-status {
          type leafref {
            path "../../state/status";
          }

          description "Related to Status";
        }

      }

    }

  }

  grouping switch-power-top {
    description "Service top";
    container switch-power {
      description "Service";
      uses switch-power-state-top;
      uses switch-power-state-attributes-top;
      uses switch-power-action;
    }

  }

  grouping embed-device-example-devices-top {
    description "Embedded devices";
    container devices {
      description "Embedded devices";
      uses child-device-name-top;
    }

  }

  grouping child-device-name-desc-top {
    description "Device description";
    container device {
      config false;
      description "Device description";
      leaf device-type {
        type string;
        description "Device type";
      }

      leaf friendly-name {
        type string;
        description "Name";
      }

      leaf manufacturer {
        type string;
        description "Manufacturer";
      }

      leaf manufacturer-URL {
        type string;
        description "Manufacturer URL";
      }

      leaf model-description {
        type string;
        description "Model description";
      }

      leaf model-name {
        type string;
        description "Model name";
      }

      leaf model-number {
        type string;
        description "Model number";
      }

      leaf model-URL {
        type string;
        description "Model URL";
      }

      leaf serial-number {
        type string;
        description "Serial number";
      }

      leaf UDN {
        type string;
        description "UUID";
      }

      leaf UPC {
        type string;
        description "UPC";
      }

      list icon-list {
        key "url";
        description  "Icons";
        leaf mimetype {
          type string;
          description "MIME type";
        }

        leaf width {
          type uint32;
          description "Width";
        }

        leaf height {
          type uint32;
          description "Height";
        }

        leaf depth {
          type uint32;
          description "Color depth";
        }

        leaf url {
          type string;
          description "URL";
        }

      }

      leaf presentation-url {
        type string;
        description "Presentation URL";
      }

    }

  }

  grouping child-device-name-services-top {
    description "Services";
    container services {
      description "Services";
      uses dimming-top;
    }

  }

  grouping dimming-state-top {
    description "State table";
    container state {
      description "State table";
      leaf load-level-target {
        type uint8 {
          range "0 .. 100";
        }

        default 0;
        description "LoadLevelTarget";
      }

      leaf load-level-status {
        type uint8 {
          range "0 .. 100";
        }

        default 0;
        config false;
        description "LoadLevelStatus";
      }

      leaf on-effect-level {
        type uint8 {
          range "0 .. 100";
        }

        default 100;
        description "OnEffectLevel";
      }

      leaf on-effect {
        type enumeration {
          enum  ON_EFFECT_LEVEL {
            description "OnEffectLevel";
          }

          enum  LAST_SETTING {
            description "LastSetting";
          }

          enum  DEFAULT {
            description "Default";
          }

        }

        default DEFAULT;
        description "OnEffect";
      }

      leaf valid-output-values {
        type string;
        config false;
        description "ValidOutputValues";
      }

      leaf step-delta {
        type uint8 {
          range "1 .. 100";
        }

        default 1;
        description "StepDelta";
      }

      leaf ramp-rate {
        type uint8 {
          range "0 .. 100";
        }

        default 0;
        description "RampRate";
      }

      leaf ramp-time {
        type uint32 {
          range "0 .. 4294967295";
        }

        default 0;
        config false;
        description "RampTime";
      }

      leaf is-ramping {
        type boolean;
        default false;
        config false;
        description "IsRamping";
      }

      leaf ramp-paused {
        type boolean;
        default false;
        config false;
        description "RampPaused";
      }

    }

  }

  grouping dimming-state-attributes-top {
    description "Table attributes";
    container state-attributes {
      config false;
      description "Read-only attributes";
      container load-level-target {
        description "Variable attributes";
        uses state-variable-attributes;
      }

      container load-level-status {
        description "Variable attributes";
        uses state-variable-attributes;
      }

      container on-effect-level {
        description "Variable attributes";
        uses state-variable-attributes;
      }

      container on-effect {
        description "Variable attributes";
        uses state-variable-attributes;
      }

      container valid-output-values {
        description "Variable attributes";
        uses state-variable-attributes;
      }

      container step-delta {
        description "Variable attributes";
        uses state-variable-attributes;
      }

      container ramp-rate {
        description "Variable attributes";
        uses state-variable-attributes;
      }

      container ramp-time {
        description "Variable attributes";
        uses state-variable-attributes;
      }

      container is-ramping {
        description "Variable attributes";
        uses state-variable-attributes;
      }

      container ramp-paused {
        description "Variable attributes";
        uses state-variable-attributes;
      }

    }

  }

  grouping dimming-action {
    description "Service actions";
    action set-load-level-target {
      description "Action SetLoadLevelTarget";
      input {
        leaf new-loadlevel-target {
          type uint8;
          description "Related to LoadLevelTarget";
        }

      }

    }

    action get-load-level-target {
      description "Action GetLoadLevelTarget";
      output {
        leaf get-loadlevel-target {
          type leafref {
            path "../../state/load-level-target";
          }

          description "Related to LoadLevelTarget";
        }

      }

    }

    action get-load-level-status {
      description "Action GetLoadLevelStatus";
      output {
        leaf ret-loadlevel-status {
          type leafref {
            path "../../state/load-level-status";
          }

          description "Related to LoadLevelStatus";
        }

      }

    }

    action set-on-effect-level {
      description "Action SetOnEffectLevel";
      input {
        leaf new-on-effect-level {
          type uint8;
          description "Related to OnEffectLevel";
        }

      }

    }

    action set-on-effect {
      description "Action SetOnEffect";
      input {
        leaf new-on-effect {
          type string;
          description "Related to OnEffect";
        }

      }

    }

    action get-on-effect-parameters {
      description "Action GetOnEffectParameters";
      output {
        leaf ret-on-effect {
          type leafref {
            path "../../state/on-effect";
          }

          description "Related to OnEffect";
        }

        leaf ret-on-effect-level {
          type leafref {
            path "../../state/on-effect-level";
          }

          description "Related to OnEffectLevel";
        }

      }

    }

    action step-up {
      description "Action StepUp";
    }

    action step-down {
      description "Action StepDown";
    }

    action start-ramp-up {
      description "Action StartRampUp";
    }

    action start-ramp-down {
      description "Action StartRampDown";
    }

    action stop-ramp {
      description "Action StopRamp";
    }

    action start-ramp-to-level {
      description "Action StartRampToLevel";
      input {
        leaf new-load-level-target {
          type uint8;
          description "Related to LoadLevelTarget";
        }

        leaf new-ramp-time {
          type uint32;
          description "Related to RampTime";
        }

      }

    }

    action set-step-delta {
      description "Action SetStepDelta";
      input {
        leaf new-step-delta {
          type uint8;
          description "Related to StepDelta";
        }

      }

    }

    action get-step-delta {
      description "Action GetStepDelta";
      output {
        leaf ret-step-delta {
          type leafref {
            path "../../state/step-delta";
          }

          description "Related to StepDelta";
        }

      }

    }

    action set-ramp-rate {
      description "Action SetRampRate";
      input {
        leaf new-ramp-rate {
          type uint8;
          description "Related to RampRate";
        }

      }

    }

    action get-ramp-rate {
      description "Action GetRampRate";
      output {
        leaf ret-ramp-rate {
          type leafref {
            path "../../state/ramp-rate";
          }

          description "Related to RampRate";
        }

      }

    }

    action pause-ramp {
      description "Action PauseRamp";
    }

    action resume-ramp {
      description "Action ResumeRamp";
    }

    action get-is-ramping {
      description "Action GetIsRamping";
      output {
        leaf ret-is-ramping {
          type leafref {
            path "../../state/is-ramping";
          }

          description "Related to IsRamping";
        }

      }

    }

    action get-ramp-paused {
      description "Action GetRampPaused";
      output {
        leaf ret-ramp-paused {
          type leafref {
            path "../../state/ramp-paused";
          }

          description "Related to RampPaused";
        }

      }

    }

    action get-ramp-time {
      description "Action GetRampTime";
      output {
        leaf ret-ramp-time {
          type leafref {
            path "../../state/ramp-time";
          }

          description "Related to RampTime";
        }

      }

    }

  }

  grouping dimming-top {
    description "Service top";
    container dimming {
      description "Service";
      uses dimming-state-top;
      uses dimming-state-attributes-top;
      uses dimming-action;
    }

  }

  grouping child-device-name-devices-top {
    description "Embedded devices";
    container devices {
      description "Embedded devices";
      uses another-grandchild-device-top;
    }

  }

  grouping child-device-name-top {
    description "child-device-name";
    container child-device-name {
      description "child-device-name";
      uses child-device-name-desc-top;
      uses child-device-name-services-top;
      uses child-device-name-devices-top;
    }

  }

  grouping another-grandchild-device-desc-top {
    description "Device description";
    container device {
      config false;
      description "Device description";
      leaf device-type {
        type string;
        description "Device type";
      }

      leaf friendly-name {
        type string;
        description "Name";
      }

      leaf manufacturer {
        type string;
        description "Manufacturer";
      }

      leaf manufacturer-URL {
        type string;
        description "Manufacturer URL";
      }

      leaf model-description {
        type string;
        description "Model description";
      }

      leaf model-name {
        type string;
        description "Model name";
      }

      leaf model-number {
        type string;
        description "Model number";
      }

      leaf model-URL {
        type string;
        description "Model URL";
      }

      leaf serial-number {
        type string;
        description "Serial number";
      }

      leaf UDN {
        type string;
        description "UUID";
      }

      leaf UPC {
        type string;
        description "UPC";
      }

      list icon-list {
        key "url";
        description  "Icons";
        leaf mimetype {
          type string;
          description "MIME type";
        }

        leaf width {
          type uint32;
          description "Width";
        }

        leaf height {
          type uint32;
          description "Height";
        }

        leaf depth {
          type uint32;
          description "Color depth";
        }

        leaf url {
          type string;
          description "URL";
        }

      }

      leaf presentation-url {
        type string;
        description "Presentation URL";
      }

    }

  }

  grouping another-grandchild-device-services-top {
    description "Services";
    container services {
      description "Services";
      uses temperature-sensor-top;
    }

  }

  grouping temperature-sensor-state-top {
    description "State table";
    container state {
      description "State table";
      leaf current-temperature {
        type int32 {
          range "0 .. 4000";
        }

        default 2000;
        config false;
        description "CurrentTemperature";
      }

      leaf application {
        type enumeration {
          enum  ROOM {
            description "Room";
          }

          enum  OUTDOOR {
            description "Outdoor";
          }

          enum  PIPE {
            description "Pipe";
          }

          enum  AIR_DUCT {
            description "AirDuct";
          }

        }

        default ROOM;
        description "Application";
      }

      leaf name {
        type string;
        description "Name";
      }

    }

  }

  grouping temperature-sensor-state-attributes-top {
    description "Table attributes";
    container state-attributes {
      config false;
      description "Read-only attributes";
      container current-temperature {
        description "Variable attributes";
        uses state-variable-attributes;
      }

      container application {
        description "Variable attributes";
        uses state-variable-attributes;
      }

      container name {
        description "Variable attributes";
        uses state-variable-attributes;
      }

    }

  }

  grouping temperature-sensor-action {
    description "Service actions";
    action get-application {
      description "Action GetApplication";
      output {
        leaf current-application {
          type leafref {
            path "../../state/application";
          }

          description "Related to Application";
        }

      }

    }

    action set-application {
      description "Action SetApplication";
      input {
        leaf new-application {
          type string;
          description "Related to Application";
        }

      }

    }

    action get-current-temperature {
      description "Action GetCurrentTemperature";
      output {
        leaf current-temp {
          type leafref {
            path "../../state/current-temperature";
          }

          description "Related to CurrentTemperature";
        }

      }

    }

    action get-name {
      description "Action GetName";
      output {
        leaf current-name {
          type leafref {
            path "../../state/name";
          }

          description "Related to Name";
        }

      }

    }

    action set-name {
      description "Action SetName";
      input {
        leaf new-name {
          type string;
          description "Related to Name";
        }

      }

    }

  }

  grouping temperature-sensor-top {
    description "Service top";
    container temperature-sensor {
      description "Service";
      uses temperature-sensor-state-top;
      uses temperature-sensor-state-attributes-top;
      uses temperature-sensor-action;
    }

  }

  grouping another-grandchild-device-devices-top {
    description "Embedded devices";
    container devices {
      description "Embedded devices";
    }

  }

  grouping another-grandchild-device-top {
    description "another-grandchild-device";
    container another-grandchild-device {
      description "another-grandchild-device";
      uses another-grandchild-device-desc-top;
      uses another-grandchild-device-services-top;
      uses another-grandchild-device-devices-top;
    }

  }

  uses embed-device-example-top;
  grouping send-events-grouping {
    description "Send event attribute";
    leaf send-events {
      type boolean;
      description "Send event attribute";
    }

  }

  grouping state-variable-attributes {
    description "upnp state variable attributes";
    uses send-events-grouping;
  }

}
